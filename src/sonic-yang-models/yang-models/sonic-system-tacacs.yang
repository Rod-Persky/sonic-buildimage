module sonic-system-tacacs {
    namespace "http://github.com/sonic-net/sonic-system-tacacs";
    prefix ssys;
    yang-version 1.1;

    import ietf-inet-types {
        prefix inet;
    }

    import sonic-port {
        prefix port;
    }

    import sonic-portchannel {
        prefix lag;
    }

    /*
    import sonic-vlan {
        prefix vlan;
    }
    */

    import sonic-loopback-interface {
        prefix loopback;
    }

    import sonic-mgmt_port {
        prefix mgmt-port;
    }

    description "Terminal Access Controller Access-Control System Plus (TACACS+) YANG module for SONiC OS.";

    revision 2021-04-15 {
        description "Initial revision.";
    }

    typedef auth_type_enumeration {
        type enumeration {
            enum pap;
            enum chap;
            enum mschap;
            enum login;
        }
    }

    typedef key_encrypt_type {
        type boolean;
        default false;
        description "Indicates if the passkey is encrypted.";
    }

    typedef epsk_hash_type {
        type enumeration {
            enum sha-256;
            enum sha-384;
        }
        default sha-256;
        description "Hash bound to the TLS 1.3 external pre-shared key.";
    }

    typedef epsk_key_exchange_type {
        type enumeration {
            enum psk-dhe;
            enum psk-only;
        }
        default psk-dhe;
        description "TLS 1.3 external pre-shared-key exchange policy.";
    }

    container sonic-system-tacacs {

        container TACPLUS_SERVER {
            description "Per-server TACACS+ configuration entries.";
            list TACPLUS_SERVER_LIST {
                description "A TACACS+ server entry identified by hostname or IP address.";
                max-elements 8;
                key "ipaddress";

                leaf ipaddress {
                    type inet:host;
                    description
                        "TACACS+ server's Domain name or IP address (IPv4 or IPv6)";
                }

                leaf priority {
                    default 1;
                    type uint8 {
                        range "1..64" {
                            error-message "TACACS server priority must be 1..64";
                        }
                    }
                    description "Server selection priority; higher values are tried first.";
                }

                leaf tcp_port {
                    type inet:port-number;
                    default 49;
                    description "TCP port used to communicate with this TACACS+ server.";
                }

                leaf timeout {
                    default 5;
                    type uint16 {
                        range "1..60" {
                            error-message "TACACS server timeout must be 1..60";
                        }
                    }
                    description "Per-server response timeout in seconds.";
                }

                leaf auth_type {
                    type auth_type_enumeration;
                    default pap;
                    description "Per-server authentication protocol (pap, chap, mschap, or login).";
                }

                leaf key_encrypt {
                    type key_encrypt_type;
                    description "Indicates whether the per-server passkey is stored encrypted.";
                }

                leaf passkey {
                    type string {
                        length "1..256";
                        pattern "[^ #,]*" {
                            error-message 'TACACS shared secret (Valid chars are ASCII printable except SPACE, "#", and ",")';
                        }
                    }
                    description "Per-server shared secret overriding the global passkey.";
                }

                leaf vrf {
                    type string {
                        pattern "mgmt|default" {
                            error-message "Error: Invalid VRF name";
                        }
                    }
                    description "VRF used to reach this TACACS+ server (mgmt or default).";
                }
            }
        }

        container TACPLUS_SERVER_TLS {
            description "Per-server TACACS+ over TLS 1.3 EPSK configuration entries.";
            list TACPLUS_SERVER_TLS_LIST {
                description "A TLS upstream identified by hostname or IP address.";
                max-elements 8;
                key "ipaddress";

                must "not(/ssys:sonic-system-tacacs/ssys:TACPLUS_SERVER/ssys:TACPLUS_SERVER_LIST[ssys:ipaddress = current()/ssys:ipaddress])" {
                    error-message "A TACACS server name or address cannot exist in both TACPLUS_SERVER and TACPLUS_SERVER_TLS";
                }

                must "not((ipaddress = 'localhost' or starts-with(ipaddress, '127.') or ipaddress = '::1') and tcp_port = /ssys:sonic-system-tacacs/ssys:TACPLUS_FORWARDER/ssys:global/ssys:local_listen_port)" {
                    error-message "A TACACS TLS upstream cannot target the local forwarder endpoint";
                }

                leaf ipaddress {
                    type inet:host;
                    description "TLS TACACS+ server domain name or IP address.";
                }

                leaf priority {
                    type uint8 {
                        range "1..64" {
                            error-message "TACACS TLS server priority must be 1..64";
                        }
                    }
                    default 1;
                    description "Server selection priority; higher values are tried first.";
                }

                leaf tcp_port {
                    type inet:port-number;
                    default 449;
                    description "TCP port used for TACACS+ over TLS.";
                }

                leaf timeout {
                    type uint16 {
                        range "1..60" {
                            error-message "TACACS TLS server timeout must be 1..60";
                        }
                    }
                    default 5;
                    description "Per-server response timeout in seconds.";
                }

                leaf domain_name {
                    type inet:domain-name;
                    description "Optional server name sent through TLS SNI.";
                }

                leaf sni_enabled {
                    type boolean;
                    default false;
                    must ". = 'false' or ../domain_name" {
                        error-message "TACACS TLS SNI requires domain_name";
                    }
                    description "Enables TLS SNI using domain_name.";
                }

                leaf single_connection {
                    type boolean;
                    default false;
                    description "Requests persistent TACACS+ connection reuse.";
                }

                leaf psk_identity {
                    type string {
                        length "1..255";
                    }
                    mandatory true;
                    description "TLS external pre-shared-key identity.";
                }

                leaf psk_secret_ref {
                    type string {
                        length "1..64";
                        pattern '[A-Za-z0-9][A-Za-z0-9_-]{0,63}' {
                            error-message "TACACS EPSK reference must be an opaque object ID";
                        }
                    }
                    mandatory true;
                    description "Opaque EPSK object ID beneath the fixed provider root.";
                }

                leaf psk_hash {
                    type epsk_hash_type;
                    description "TLS 1.3 EPSK handshake hash.";
                }

                leaf psk_key_exchange {
                    type epsk_key_exchange_type;
                    must ". != 'psk-only' or not(../psk_key_exchange_groups)" {
                        error-message "TACACS TLS psk-only mode cannot configure DHE groups";
                    }
                    description "TLS 1.3 EPSK key-exchange policy.";
                }

                leaf psk_key_exchange_groups {
                    type string {
                        pattern '(x25519|secp256r1|secp384r1|secp521r1|ffdhe2048|ffdhe3072|ffdhe4096|ffdhe6144|ffdhe8192)(:(x25519|secp256r1|secp384r1|secp521r1|ffdhe2048|ffdhe3072|ffdhe4096|ffdhe6144|ffdhe8192))*' {
                            error-message "TACACS TLS PSK-DHE groups must be a colon-separated supported group list";
                        }
                    }
                    description "Optional ordered PSK-DHE groups; absence uses implementation defaults.";
                }
            }
        }

        container TACPLUS_FORWARDER {
            description "Bind-time settings for the local TACACS+ central agent.";
            container global {
                presence "Enables explicit local TACACS+ forwarder settings.";
                leaf local_listen_address {
                    type inet:ip-address;
                    mandatory true;
                    must "starts-with(., '127.') or . = '::1'" {
                        error-message "TACACS forwarder listen address must be loopback";
                    }
                    description "Host-loopback address for the compatibility listener.";
                }

                leaf local_listen_port {
                    type inet:port-number;
                    default 49;
                    description "TCP port for the compatibility listener.";
                }
            }
        }

        container TACPLUS {
            description "Global TACACS+ client configuration.";

            container global {
                description "Global TACACS+ authentication settings applied to all servers.";

                leaf auth_type {
                    type auth_type_enumeration;
                    default pap;
                    description "Default authentication protocol for TACACS+ communication.";
                }

                leaf timeout {
                    type uint16 {
                        range "1..60" {
                            error-message "TACACS timeout must be 1..60";
                        }
                    }
                    default 5;
                    description "Default timeout in seconds for TACACS+ server responses.";
                }

                leaf key_encrypt {
                    type key_encrypt_type;
                    description "Indicates whether the global passkey is stored encrypted.";
                }

                leaf passkey {
                    type string {
                        length "1..256";
                        pattern "[^ #,]*" {
                            error-message 'TACACS shared secret (Valid chars are ASCII printable except SPACE, "#", and ",")';
                        }
                    }
                    description "Default shared secret for authenticating TACACS+ server communication.";
                }

                leaf src_intf {
                    type union {
                        type leafref {
                            path "/port:sonic-port/port:PORT/port:PORT_LIST/port:name";
                        }
                        type leafref {
                            path "/lag:sonic-portchannel/lag:PORTCHANNEL/lag:PORTCHANNEL_LIST/lag:name";
                        }
                        /*
                        type leafref {
                            path "/vlan:sonic-vlan/vlan:VLAN/vlan:VLAN_LIST/vlan:name";
                        }
                        */
                        type string {
                            pattern 'Vlan([0-9]{1,3}|[1-3][0-9]{3}|[4][0][0-8][0-9]|[4][0][9][0-4])';
                        }
                        type leafref {
                            path "/loopback:sonic-loopback-interface/loopback:LOOPBACK_INTERFACE/loopback:LOOPBACK_INTERFACE_LIST/loopback:name";
                        }
                        type leafref {
                            path "/mgmt-port:sonic-mgmt_port/mgmt-port:MGMT_PORT/mgmt-port:MGMT_PORT_LIST/mgmt-port:name";
                        }
                    }
                    description "Source interface whose IP address is used for outgoing TACACS+ packets.";
                }
            }
        }
    }
}
